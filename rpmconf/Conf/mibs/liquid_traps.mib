LIQUID-TRAP-MIB DEFINITIONS ::= BEGIN
        IMPORTS liquid FROM LIQUID-MIB;

lqtraps OBJECT IDENTIFIER ::= { liquid 0 }

lqServiceStatusTrap NOTIFICATION-TYPE
        STATUS current
        DESCRIPTION "Service Status Change"
        ::= { lqtraps 0 }

END
